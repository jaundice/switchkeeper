SWITCHKEEPER-TEST-MIB DEFINITIONS ::= BEGIN

IMPORTS
    MODULE-IDENTITY, OBJECT-TYPE, enterprises, Integer32
        FROM SNMPv2-SMI;

skTest MODULE-IDENTITY
    LAST-UPDATED "202606010000Z"
    ORGANIZATION "Switchkeeper"
    CONTACT-INFO  "https://github.com/jaundice/switchkeeper"
    DESCRIPTION   "Tiny self-contained MIB used by the loader unit tests."
    REVISION      "202606010000Z"
    DESCRIPTION   "Initial."
    ::= { enterprises 99999 }

skScalar OBJECT-TYPE
    SYNTAX      Integer32
    MAX-ACCESS  read-write
    STATUS      current
    DESCRIPTION "A writable scalar at 1.3.6.1.4.1.99999.1"
    ::= { skTest 1 }

skReadOnly OBJECT-TYPE
    SYNTAX      Integer32
    MAX-ACCESS  read-only
    STATUS      current
    DESCRIPTION "A read-only scalar at 1.3.6.1.4.1.99999.2"
    ::= { skTest 2 }

END
